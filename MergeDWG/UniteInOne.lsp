(defun c:ii() (command"_insert""ИВЕЖ.687445.002-1697-20ПН_1.dwg""МАСШТАБ""1""ПОВОРОТ""0""0,0")(command"_insert""ИВЕЖ.687445.002-1697-20ПН_2.dwg""МАСШТАБ""1""ПОВОРОТ""0""500,0")(command"_insert""ИВЕЖ.687445.002-1697-20ПН_3.dwg""МАСШТАБ""1""ПОВОРОТ""0""1000,0")(command"_insert""ИВЕЖ.687445.002-1697-20ПЭ3_1.dwg""МАСШТАБ""1""ПОВОРОТ""0""1500,0")(command"_insert""ИВЕЖ.687445.002-1697-20ТЭ4_1.dwg""МАСШТАБ""1""ПОВОРОТ""0""2000,0")(command"_insert""ИВЕЖ.687445.002-1697-20ТЭ4_2.dwg""МАСШТАБ""1""ПОВОРОТ""0""2500,0")(command"_insert""ИВЕЖ.687445.002-1697-20ТЭ4_3.dwg""МАСШТАБ""1""ПОВОРОТ""0""3000,0")(command"_insert""ИВЕЖ.687445.002-1697-20ТЭ4_4.dwg""МАСШТАБ""1""ПОВОРОТ""0""3500,0")(command"_insert""ИВЕЖ.687445.002-1697-20Э3_1.dwg""МАСШТАБ""1""ПОВОРОТ""0""4000,0"))
